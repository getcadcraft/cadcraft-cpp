(vl-string-search "a" "banana" 2)
(vl-string-search "" "abc" 10)
(vl-string-search "a" "banana" -5)
(vl-string-search "😀" "x😀")
(vl-string-search 1 "a")
(vl-string-search "a" 1)
(vl-string-subst "x" "a" "banana" 2)
(vl-string-subst "x" "" "abc")
(vl-string-subst "x" "z" "abc")
(vl-string-trim "ab" "abcba")
(vl-string-right-trim " \t" "x \t ")
(vl-string-left-trim "" "abc")
(vl-string-translate "abc" "x" "aabbcc")
(vl-string-translate "abc" "" "abc")
(vl-string-translate "😀" "x" "a😀b")
(vl-string-translate "a" "😀" "aa")
(vl-string-position 97 "banana" nil t)
(vl-string-position 97 "banana" 2)
(vl-string-position 97 "banana" 2 t)
(vl-string-position 122 "abc")
(vl-string-position 97 "" nil t)
(vl-string-position 97 "abc" -3 t)
(vl-string-position 97 "abc" 99)
(vl-string-position 65633 "a")
(vl-string-mismatch "abcd" "abxd")
(vl-string-mismatch "ABc" "abC" 0 0 t)
(vl-string-mismatch "abc" "xbc" 1 1)
(vl-string-mismatch "ab" "ab" -1 -1)
(vl-string-mismatch "ab" "ab" -1 -1 t)
(vl-string-mismatch "ab" "ab" 0.0 0)
(vl-string-mismatch "ab" "ab" 1.5)
(vl-string-mismatch "straße" "STRASSE" 0 0 t)
(vl-string-elt "abc" 3)
(vl-string-elt "😀" 1)
(vl-string->list "a😀")
(vl-list->string '(55357 56832))
(vl-list->string nil)
(vl-list->string '(65 1.0))
(vl-princ-to-string '("a" 1.5 b))
(vl-prin1-to-string (quote (quote x)))
(vl-prin1-to-string '(quote x y))
(vl-prin1-to-string '(1 . (2 . 3)))
(vl-symbol-name 'straße)
(vl-symbol-name "x")
(vl-symbolp 'a)
(vl-symbolp nil)
