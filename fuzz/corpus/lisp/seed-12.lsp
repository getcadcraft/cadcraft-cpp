(defun g (/ *error*) (defun *error* (m) (princ (strcat "caught:" m))) (car 1)) (g)
(car 1)
*error*
(setq x 1) (defun h (/ x) (setq x 2) (k)) (defun k () x)
(h)
x
(defun *error* (m) (princ (strcat "E:" m))) (car 1)
(exit)
(quit)
(vl-exit-with-value 5)
(vl-exit-with-error "boom")
(defun *error* (m) (car 2)) (car 1)
(defun *error* (m) (car 1)) (car 1)
(setq *error* "x") (car 1)
(setq *error* '((m) (princ (list 'got m)))) (car 1)
(setq *error* princ) (car 1)
(setq *error* quote) (car 1)
(setq *error* nil) (defun inner () (car 1)) (defun outer (/ *error*) (defun *error* (m) (princ "outer:")) (inner)) (outer)
(defun f (a / b) (setq b 5) (car a)) (setq a 1 b 2) (f 3)
(list a b)
(setq v 1) (foreach v '(7 8) (princ v)) v
(defun fe () (foreach v '(1 2) (car v))) (fe) v
(defun *error* (m) (princ (strcat "[" m "]")) (princ (list a b))) (f 9)
(setq *error* nil)
(vl-catch-all-apply 'car '(1))
(type (vl-catch-all-apply 'car '(1)))
(defun *error* (m) (princ "no")) (vl-catch-all-apply '(lambda () (car 1)) nil)
(vl-catch-all-error-message (vl-catch-all-apply 'exit nil))
(vl-catch-all-error-message (vl-catch-all-apply 'zzz nil))
(vl-catch-all-error-message (vl-catch-all-apply '+ 5))
(vl-catch-all-error-message 5)
(vl-catch-all-error-p 5)
(setq *error* nil)
(vl-catch-all-apply '(lambda (x) (vl-catch-all-apply 'car (list x))) '(1))
