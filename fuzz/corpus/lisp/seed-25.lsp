(strcat)
(strcat "a" 1)
(strlen)
(strlen "héllo")
(strlen "😀")
(substr "héllo" 2 2)
(substr "😀x" 2)
(substr "abc" 0)
(substr "abc" 2 -1)
(substr "abc" 5)
(substr "abc" 2 0)
(substr "abc" 1 nil)
(strcase "straße")
(strcase "ÀÉÎ" t)
(strcase "ǅ")
(strcase "a" nil)
(ascii "")
(ascii "é")
(ascii "😀")
(chr 233)
(chr 0)
(chr 65601)
(strlen (chr 55357))
(strcat (chr 55357) (chr 56832))
(strlen (strcat (chr 55357) (chr 56832)))
(chr -1)
(itoa -5)
(itoa 5.0)
(atoi " -12x")
(atoi "x")
(atoi "99999999999")
(atoi "+7")
(atof "  -1.5e3x")
(atof ".e5")
(atof "1e")
(atof "Infinity")
(atof "-.5")
(atof "1.5E+2")
(atof "")
(prin1 "a\"b\\c\e")
(vl-prin1-to-string "x\ty")
"\q"
(ascii "\7")
"\1011"
"\777"
(strlen "\0")
"a\\b"
"multi
line"
