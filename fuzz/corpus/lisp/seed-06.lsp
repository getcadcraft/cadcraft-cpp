(if)
(if t)
(if t 1 2 3)
(cond)
(cond (nil 1) (2))
(cond 5)
(cond (1 . 2))
(while nil 1)
(repeat 0 1)
(repeat -1 1)
(repeat 2.0 1)
(repeat)
(foreach)
(foreach x)
(foreach x 5)
(foreach 5 '(1))
(foreach x '(1 2 . 3) (princ x))
(setq)
(setq a)
(setq 5 1)
(setq a 1 b)
a
(progn)
(and nil (car 1))
(or 1 (car 1))
(quote)
(quote 1 2)
(function car)
(function (lambda (x) x))
(function zzz)
(function 'a)
((lambda (x) (* x x)) 3)
((function +) 1 2)
("a" 1)
(1 2)
(nil)
(setq q 5) (q)
(setq q 'car) (q '(1 2))
(setq q '(lambda (x) x)) (q 7)
(setq q '((x) (* x 2))) (q 4)
(setq q '((x / y) (setq y x) (list x y))) (q 4)
(eval 'pi)
(eval 5)
(eval '(quote x))
(eval)
(lambda)
(lambda 5)
(lambda (1) 1)
(defun)
(defun 5 ())
(defun f)
(defun f (a / b c) (list a b c)) (f 1)
(defun f (a b) (list a b)) (f 1)
(f 1 2 3)
(defun c: () 1)
(defun c:hello () (princ "hi") (princ))
(defun c:two () 2)
(defun c:HELLO () (princ "again") (princ))
(defun-q dq (x) x) (dq 3)
(defun f (a a) a) (f 1 2)
(defun f (/ x x) x) (f)
