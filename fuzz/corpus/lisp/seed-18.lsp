(vl-sort '(3 1 2 5 4) '(lambda (a b) (princ (list a b)) (< a b)))
(vl-sort '((1 . a) (0 . b) (1 . c)) '(lambda (x y) (< (car x) (car y))))
(vl-sort-i '(3 1 2) '>)
(vl-sort 5 '<)
(vl-sort '(1 2) 'zzz)
(vl-sort nil '<)
(vl-sort '(1) 'zzz)
(vl-sort '("b" "a") '>)
(vl-sort-i '(2 2 1) '<)
(vl-sort '(3 2 1) '(lambda (a b) (car 1)))
