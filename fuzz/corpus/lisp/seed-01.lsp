(open "x" "q")
(open "x" "")
(open "nope.txt" "r")
(setq f (open "W.TXT" "W")) (write-line "a" f) (write-char 65 f) (princ "p" f) (prin1 "q" f) (print 1 f) (close f)
(setq f (open "w.txt" "r")) (list (read-char f) (read-line f) (read-line f) (read-line f) (read-line f))
(close f) (read-char f)
(read-line f)
(close 5)
(read-line 5)
(write-line "x" 5)
(write-line 5)
(write-line "x" f)
(setq g (open "w.txt" "a")) (write-line "more" g) (close g) (setq g (open "w.txt" "r")) (list (read-line g) (read-line g) (read-line g) (read-line g) (read-line g))
(vl-file-size "w.txt")
(vl-file-size "none")
(vl-file-rename "w.txt" "b.txt")
(vl-file-rename "nope" 5)
(vl-file-rename "b.txt" "b.txt")
(findfile "w.txt")
(findfile "B.TXT")
(vl-file-copy "b.txt" "d/c.txt")
(vl-file-copy "b.txt" "d/c.txt" t)
(vl-file-size "c.txt")
(vl-directory-files nil "*.TXT")
(vl-directory-files)
(vl-directory-files "x" "?.txt")
(vl-directory-files "x" "")
(vl-file-delete "b.txt")
(vl-file-delete "b.txt")
(vl-file-delete "C.TXT")
(vl-file-delete "d\\c.txt")
(vl-filename-mktemp)
(vl-filename-mktemp "abc.tmp")
(vl-filename-mktemp "x" "c:\\dir\\" ".dat")
(vl-filename-mktemp "" "" "")
(vl-filename-mktemp 5)
(vl-filename-mktemp "a.b.c")
(vl-filename-directory "a/b\\c.txt")
(vl-filename-directory "c.txt")
(vl-filename-base "a.b.c")
(vl-filename-base "dir.x/abc")
(vl-filename-extension "noext")
(vl-filename-extension "a.")
(vl-filename-extension "d.x/abc")
(vl-file-directory-p "x")
(vl-mkdir "x")
(vl-registry-read "x")
(setq f (open "crlf.txt" "w")) (princ "a\r\nb\r\n\r\nc" f) (close f) (setq f (open "crlf.txt" "r")) (list (read-line f) (read-line f) (read-line f) (read-line f) (read-line f))
(setq f (open "u.txt" "w")) (write-line "é😀" f) (close f) (setq f (open "u.txt" "r")) (list (read-char f) (read-char f) (read-char f) (read-line f))
(vl-file-size "u.txt")
(defun tool () "tool")
(defun c:tool () (princ (tool)) (princ))
(findfile "tools.lsp")
(findfile "c:/lisp/TOOLS.LSP")
(load "Tools") (tool)
(load "c:\\lisp\\tools.lsp")
(load 5)
(load "nothere")
(load "x" nil)
(defun broken () (car 1)

(load "broken")
(vl-catch-all-error-message (vl-catch-all-apply (quote load) (list "broken")))
(defun x () 1))
; a routine
(defun c:greet (/ n) (setq n "you") (princ (strcat "hello " n)) (princ))
(defun helper (a) (* a 2))
(princ "loaded")
(helper 21)
(princ "start")
(car 1)
(princ "never")
(load "good")
