(cdr '(1 . 2))
(cadr '(1))
(caddr '(1 2 3))
(cddddr '(1 2 3 4 5))
(caaaar '((((1)))))
(car "x")
(cdr 5)
(cadr '(1 . 2))
(nth -1 '(1))
(nth 0 nil)
(nth 1 '(1 . 2))
(nth 1.0 '(1 2))
(last nil)
(last '(1 2 . 3))
(length '(1 . 2))
(length "abc")
(length nil)
(append '(1 . 2) '(3))
(append '(1) 2)
(append)
(append nil)
(reverse nil)
(reverse '(1 . 2))
(member 2.0 '(1 2 3))
(member "b" '("a" "b"))
(member 1 5)
(assoc "b" '(("a" . 1) ("b" . 2)))
(assoc 1 '(1 (1 . 2)))
(subst 1 2 '(2 (2) 2))
(subst 1 2 '(1 . 2))
(subst 1 2 5)
(acad_strlsort '("b" "A" "a" "B" "é" "E"))
(acad_strlsort '(1))
(list 1 'a "s" 2.5 nil)
(cons nil nil)
(cons 1 nil)
(cons 1)
(vl-list* 1)
(vl-list* 1 2)
(vl-list*)
(vl-list-length '(1 . 2))
(vl-list-length '(1 2))
(vl-list-length 5)
(vl-consp nil)
(vl-consp '(1))
(vl-position 2 '(1 2 3 2))
(vl-position 2 '(1 . 2))
(vl-remove 'a nil)
(vl-remove 1.0 '(1 2 1))
(vl-remove-if-not 'numberp 5)
(vl-member-if-not 'numberp '(1 a 2))
(vl-some '= '(1 2 3) '(3 2 1))
(vl-every '< '(1 2) '(2 3 0))
(vl-every 'numberp nil)
(vl-some 'numberp)
(mapcar 'car '((1) (2)))
(mapcar '+ '(1 2) nil)
(mapcar 'zzz '(1))
(mapcar '+)
(apply '+ 5)
(apply 5 nil)
(apply 'quote '(1))
(apply 'if '(t 1))
(apply '(lambda (a b) (- a b)) '(5 3))
(apply (function max) '(1 9 3))
