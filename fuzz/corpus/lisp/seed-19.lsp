(setq x nil) (repeat 300 (setq x (list x))) (vl-prin1-to-string x)
(setq l nil) (repeat 100005 (setq l (cons 1 l))) (strlen (vl-prin1-to-string l))
(setq a 1 b 1) (repeat 5000 (setq a (list a) b (list b))) (equal a b)
(setq l nil) (repeat 130000 (setq l (cons 1 l))) (length (append l))
(apply 'max l)
(length (append (reverse l)))
(setq l nil) (repeat 1000 (setq l (cons 1 l))) (length (append l l l))
(setq a 'b b 'a) (apply 'a nil)
(a)
(setq x 1) (repeat 1000 (setq x (list '1+ x))) (eval x)
(setq x 1) (repeat 3000 (setq x (list 'quote x))) (length (eval x))
