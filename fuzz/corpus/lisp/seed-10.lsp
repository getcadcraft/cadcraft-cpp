(+ 1 2)
(/ 7 2)
(/ 7 2.0)
(+ 1 2.0)
'(1 . 2)
(cadr (list 1 2 3))
(setq a 5) (* a a)
(defun sq (x / y) (setq y (* x x)) y) (sq 4)
y
(mapcar '(lambda (x) (* 2 x)) '(1 2 3))
(mapcar (function 1+) '(1 2))
(mapcar '+ '(1 2 3) '(10 20))
(strcat "a" "b")
(substr "hello" 2 3)
(substr "hello" 3)
(strlen "abc" "de")
(wcmatch "BLOCK1" "BLOCK#")
(wcmatch "abc" "*break,*cancel*,*exit*")
(wcmatch "Function cancelled" "*cancel*")
(wcmatch "A-12" "~*-##")
(wcmatch "x" "[a-z]")
(wcmatch "*" "`*")
(wcmatch "door" "@@@@")
(rtos 3.14159 2 2)
(rtos 2.5 2 3)
(rtos 18.5 4 2)
(rtos 0.5 5 2)
(angtos pi 0 2)
(angtos (/ pi 4) 1 4)
(angtos (/ pi 4) 1 2)
(angtos pi 3 2)
(angtof "90")
(distof "12.5")
(polar '(0 0) 0 5)
(polar '(1 1 1) (/ pi 2) 2)
(distance '(0 0) '(3 4))
(angle '(0 0) '(0 -1))
(inters '(0 0) '(10 10) '(0 10) '(10 0))
(inters '(0 0) '(1 1) '(0 10) '(10 0))
(inters '(0 0) '(1 1) '(0 10) '(10 0) nil)
(assoc 2 '((1 . "a") (2 . "b")))
(cond ((= 1 2) "no") (t "yes"))
(cond ((+ 1 2)))
(setq i 0) (while (< i 10) (setq i (1+ i))) i
(setq s 0) (foreach x '(1 2 3) (setq s (+ s x))) s
(repeat 3 (setq s (1+ s)))
(apply '+ '(1 2 3))
(vl-load-com)
(type 1)
(type 1.0)
(type "a")
(type 'a)
(type nil)
(type car)
(car nil)
(rem 7 3)
(rem -7 3)
(boole 6 5 3)
(boole 1 12 5)
(boole 7 12 5)
(logand 125 64)
(logior 1 2 4)
(lsh 1 4)
(~ 0)
(read "(1 2)")
(eval '(+ 1 1))
(nth 1 '(a b c))
(nth 5 '(a b c))
(member 2 '(1 2 3))
(1+ 2147483647)
(equal '(1 2.0) '(1 2.0001) 0.001)
(equal '(1 2.0) '(1 2.0001))
(eq 'a 'a)
(eq '(1) '(1))
(= 1 1.0)
(= "a" "a")
(/= 1 2 1)
(fix 3.7)
(fix -3.7)
(float 3)
(atof "2.5mm")
(atoi "42abc")
(itoa 42)
(chr 65)
(ascii "A")
(strcase "abc")
(strcase "ABC" t)
(abs -2)
(min 1 2.0)
(max 1 2)
(sqrt 16)
(expt 2 10)
(expt 2.0 0.5)
(gcd 12 18)
(atan 1 1)
(sin 0)
(exp 0)
(log 1)
(append '(1) '(2 3) nil '(4))
(reverse '(1 2 3))
(length '(1 2 3))
(last '(1 2 3))
(subst 'x 'b '(a b c b))
(cons 1 '(2))
(cons 1 2)
(list)
(not nil)
(null 0)
(atom 1)
(listp nil)
(boundp 'zzz)
(and 1 2)
(and)
(or nil nil)
(if nil 1)
(if 0 1 2)
(progn 1 2 3)
(set 'q 7) q
(vl-sort '(3 1 2) '<)
(vl-sort '("b" "A" "c") '<)
(vl-sort-i '(30 10 20) '<)
(vl-remove-if '(lambda (x) (> x 1)) '(1 2 3))
(vl-remove-if-not 'numberp '(1 "a" 2))
(vl-remove 2 '(1 2 3 2))
(vl-position 'c '(a b c))
(vl-some 'minusp '(1 -2))
(vl-every 'numberp '(1 2))
(vl-member-if 'minusp '(1 -2 3))
(vl-string-search "lo" "hello")
(vl-string-search "z" "hello")
(vl-string-subst "J" "h" "hah")
(vl-string-trim " " "  x  ")
(vl-string-trim "()" "(0 1)")
(vl-string-left-trim "0" "007")
(vl-string-translate "ab" "xy" "abc")
(vl-string->list "AB")
(vl-list->string '(72 105))
(vl-princ-to-string "a")
(vl-prin1-to-string "a")
(vl-princ-to-string '(0 1))
(vl-symbol-name 'abc)
(vl-list* 1 2 '(3))
(vl-string-position (ascii "l") "hello")
(vl-filename-base "c:\\dir\\a.lsp")
(vl-filename-extension "a.dcl")
(cvunit 1 "inch" "mm")
(cvunit 180 "degree" "radian")
(vl-catch-all-error-p (vl-catch-all-apply '/ '(1 0)))
(vl-catch-all-error-message (vl-catch-all-apply '/ '(1 0)))
(vl-catch-all-apply '+ '(1 2))
(car 1)
(foo)
(sqrt -1)
(1+ "a")
(defun f2 (a) a) (f2)
(defun f3 () 1) (f3 2)
;| inline |; (+ 1 ;| x |; 2)
"a\nb"
"tab\t"
"\101"
1.
.5
1e3
-3
3000000000
'(a . (b c))
(quote (1 2))
(read "x")
(atoms-family 1 '("CAR" "ZZZQQ"))
(ver)
