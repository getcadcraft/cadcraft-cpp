(rtos 3.14159)
(rtos 1234.5 1 3)
(rtos 0.0 1 2)
(rtos -1234.5 1 3)
(rtos 15.75 3 2)
(rtos 15.75 4 4)
(rtos -15.75 4 4)
(rtos 0.0 4 2)
(rtos 2.375 5 3)
(rtos 0.001 2 2)
(rtos -0.001 2 2)
(rtos 1e25 2 2)
(rtos 1.5 6)
(rtos 1.5 0 2)
(rtos 1.5 2 20)
(rtos 1.5 2 -3)
(rtos "x")
(rtos 2.5 2 0)
(rtos 1.005 2 2)
(rtos 12 2 2)
(rtos 0.5 5 0)
(rtos 100.0 3 0)
(rtos 1e-310 1 3)
(rtos 5 nil 3)
(rtos 5 2 nil)
(rtos 5 2.0)
